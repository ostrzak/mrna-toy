"""Open the adjacent V7 handheld model and its optional controls."""
from pathlib import Path
import importlib
import sys
import FreeCAD as App

sys.dont_write_bytecode=True
folder=Path(__file__).resolve().parent
if str(folder) in sys.path:
    sys.path.remove(str(folder))
sys.path.insert(0,str(folder))
import bracelet_v7
model=importlib.reload(bracelet_v7)
target=(folder/model.MODEL_FILE).resolve()
doc=next((d for d in App.listDocuments().values() if d.FileName and Path(d.FileName).resolve()==target),None)
if doc is None:
    doc=App.openDocument(str(target))
App.setActiveDocument(doc.Name)
model.present(doc)
controls=model.open_controls(doc)
