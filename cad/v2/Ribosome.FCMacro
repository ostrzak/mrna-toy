"""Open the V2 RNA-dial cuff, feed and swivel controls in FreeCAD."""
from pathlib import Path
import sys
import importlib.util
import FreeCAD as App

sys.dont_write_bytecode=True
folder=Path(__file__).resolve().parent
spec=importlib.util.spec_from_file_location('mrna_toy_v2',folder/'bracelet.py')
bracelet=importlib.util.module_from_spec(spec)
sys.modules[spec.name]=bracelet
spec.loader.exec_module(bracelet)
target=(folder/'Ribosome.FCStd').resolve()
doc=next((d for d in App.listDocuments().values() if d.FileName and Path(d.FileName).resolve()==target),None)
if doc is None:
    doc=App.openDocument(str(target))
App.setActiveDocument(doc.Name)
bracelet.present(doc)
controls=bracelet.open_controls(doc)
